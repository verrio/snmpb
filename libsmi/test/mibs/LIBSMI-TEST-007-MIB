LIBSMI-TEST-007-MIB DEFINITIONS ::= BEGIN

IMPORTS
    MODULE-IDENTITY
	FROM SNMPv2-SMI
    testMib
        FROM LIBSMI-TEST-MIB;

libsmiTest007Mib MODULE-IDENTITY
    LAST-UPDATED    "199906221500Z"
    ORGANIZATION    
            "TU Braunschweig"
    CONTACT-INFO    
            "        Frank Strauss
             
             Postal: TU Braunschweig
                     Bueltenweg 74/75
                     38106 Braunschweig
                     Germany
             
              Phone: +49 531 391-3283
              EMail: strauss@ibr.cs.tu-bs.de
               http://www.ibr.cs.tu-bs.de/~strauss/"
    DESCRIPTION     
            "This MIB module contains one or more intentional errors,
             and/or unusual contents. Its only purpose is to check
             the abilities of MIB parsers to detect these circumstances.
             
             This MIB module is orginally written in SMIv2 format.
             
             A MIB parser should complain about the fact, that `mib-2'
	     is used in the definition of `libsmiTest007Junk', but not
	     known (neither imported, nor defined).

	     The libsmi parser is expected to report:
LIBSMI-TEST-007-MIB:44: unknown object identifier label `mib-2'
	     "
    REVISION        "199906221500Z"
    DESCRIPTION     
            "Initial Revision."
    ::= { testMib 7 }

libsmiTest007Junk OBJECT IDENTIFIER
    ::= { mib-2 42 }

END
