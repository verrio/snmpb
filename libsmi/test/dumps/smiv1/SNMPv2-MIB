--
-- This SMIv1 module has been generated by smidump 0.4.5. Do not edit.
--

SNMPv2-MIB DEFINITIONS ::= BEGIN

IMPORTS
    OBJECT-TYPE
        FROM RFC-1212
    TRAP-TYPE
        FROM RFC-1215
    Counter, TimeTicks
        FROM RFC1155-SMI
    mib-2
        FROM RFC1213-MIB
    snmpModules
        FROM SNMPv2-SMI
    DisplayString, TestAndIncr, TimeStamp
        FROM SNMPv2-TC;

snmpMIB OBJECT IDENTIFIER
    ::= { snmpModules 1 }

-- snmpMIB MODULE-IDENTITY
--     LAST-UPDATED "200210160000Z"
--     ORGANIZATION 
--         "IETF SNMPv3 Working Group"
--     CONTACT-INFO 
--         "WG-EMail:   snmpv3@lists.tislabs.com
--          Subscribe:  snmpv3-request@lists.tislabs.com
--          
--          Co-Chair:   Russ Mundy
--                      Network Associates Laboratories
--          postal:     15204 Omega Drive, Suite 300
--                      Rockville, MD 20850-4601
--                      USA
--          EMail:      mundy@tislabs.com
--          phone:      +1 301 947-7107
--          
--          Co-Chair:   David Harrington
--                      Enterasys Networks
--          postal:     35 Industrial Way
--                      P. O. Box 5005
--                      Rochester, NH 03866-5005
--                      USA
--          EMail:      dbh@enterasys.com
--          phone:      +1 603 337-2614
--          
--          Editor:     Randy Presuhn
--                      BMC Software, Inc.
--          postal:     2141 North First Street
--                      San Jose, CA 95131
--                      USA
--          EMail:      randy_presuhn@bmc.com
--          phone:      +1 408 546-1006"
--     DESCRIPTION 
--         "The MIB module for SNMP entities.
--          
--          Copyright (C) The Internet Society (2002). This
--          version of this MIB module is part of RFC 3418;
--          see the RFC itself for full legal notices."
--     REVISION    "200210160000Z"
--     DESCRIPTION 
--         "This revision of this MIB module was published as
--          RFC 3418."
--     REVISION    "199511090000Z"
--     DESCRIPTION 
--         "This revision of this MIB module was published as
--          RFC 1907."
--     REVISION    "199304010000Z"
--     DESCRIPTION 
--         "The initial revision of this MIB module was published
--          as RFC 1450."
--     ::= { snmpModules 1 }


system OBJECT IDENTIFIER
    ::= { mib-2 1 }

sysDescr OBJECT-TYPE
    SYNTAX      DisplayString (SIZE(0..255))
    ACCESS      read-only
    STATUS      mandatory
    DESCRIPTION 
        "A textual description of the entity.  This value should
         include the full name and version identification of
         the system's hardware type, software operating-system,
         and networking software."
    ::= { system 1 }

sysObjectID OBJECT-TYPE
    SYNTAX      OBJECT IDENTIFIER
    ACCESS      read-only
    STATUS      mandatory
    DESCRIPTION 
        "The vendor's authoritative identification of the
         network management subsystem contained in the entity.
         This value is allocated within the SMI enterprises
         subtree (1.3.6.1.4.1) and provides an easy and
         unambiguous means for determining `what kind of box' is
         being managed.  For example, if vendor `Flintstones,
         Inc.' was assigned the subtree 1.3.6.1.4.1.424242,
         it could assign the identifier 1.3.6.1.4.1.424242.1.1
         to its `Fred Router'."
    ::= { system 2 }

sysUpTime OBJECT-TYPE
    SYNTAX      TimeTicks
    ACCESS      read-only
    STATUS      mandatory
    DESCRIPTION 
        "The time (in hundredths of a second) since the
         network management portion of the system was last
         re-initialized."
    ::= { system 3 }

sysContact OBJECT-TYPE
    SYNTAX      DisplayString (SIZE(0..255))
    ACCESS      read-write
    STATUS      mandatory
    DESCRIPTION 
        "The textual identification of the contact person for
         this managed node, together with information on how
         to contact this person.  If no contact information is
         known, the value is the zero-length string."
    ::= { system 4 }

sysName OBJECT-TYPE
    SYNTAX      DisplayString (SIZE(0..255))
    ACCESS      read-write
    STATUS      mandatory
    DESCRIPTION 
        "An administratively-assigned name for this managed
         node.  By convention, this is the node's fully-qualified
         domain name.  If the name is unknown, the value is
         the zero-length string."
    ::= { system 5 }

sysLocation OBJECT-TYPE
    SYNTAX      DisplayString (SIZE(0..255))
    ACCESS      read-write
    STATUS      mandatory
    DESCRIPTION 
        "The physical location of this node (e.g., 'telephone
         closet, 3rd floor').  If the location is unknown, the
         value is the zero-length string."
    ::= { system 6 }

sysServices OBJECT-TYPE
    SYNTAX      INTEGER (0..127)
    ACCESS      read-only
    STATUS      mandatory
    DESCRIPTION 
        "A value which indicates the set of services that this
         entity may potentially offer.  The value is a sum.
         
         
         
         This sum initially takes the value zero. Then, for
         each layer, L, in the range 1 through 7, that this node
         performs transactions for, 2 raised to (L - 1) is added
         to the sum.  For example, a node which performs only
         routing functions would have a value of 4 (2^(3-1)).
         In contrast, a node which is a host offering application
         services would have a value of 72 (2^(4-1) + 2^(7-1)).
         Note that in the context of the Internet suite of
         protocols, values should be calculated accordingly:
         
              layer      functionality
                1        physical (e.g., repeaters)
                2        datalink/subnetwork (e.g., bridges)
                3        internet (e.g., supports the IP)
                4        end-to-end  (e.g., supports the TCP)
                7        applications (e.g., supports the SMTP)
         
         For systems including OSI protocols, layers 5 and 6
         may also be counted."
    ::= { system 7 }

sysORLastChange OBJECT-TYPE
    SYNTAX      TimeStamp
    ACCESS      read-only
    STATUS      mandatory
    DESCRIPTION 
        "The value of sysUpTime at the time of the most recent
         change in state or value of any instance of sysORID."
    ::= { system 8 }

sysORTable OBJECT-TYPE
    SYNTAX      SEQUENCE OF SysOREntry
    ACCESS      not-accessible
    STATUS      mandatory
    DESCRIPTION 
        "The (conceptual) table listing the capabilities of
         the local SNMP application acting as a command
         responder with respect to various MIB modules.
         SNMP entities having dynamically-configurable support
         of MIB modules will have a dynamically-varying number
         of conceptual rows."
    ::= { system 9 }

sysOREntry OBJECT-TYPE
    SYNTAX      SysOREntry
    ACCESS      not-accessible
    STATUS      mandatory
    DESCRIPTION 
        "An entry (conceptual row) in the sysORTable."
    INDEX       { sysORIndex }
    ::= { sysORTable 1 }

SysOREntry ::= SEQUENCE {
    sysORIndex      INTEGER,
    sysORID         OBJECT IDENTIFIER,
    sysORDescr      DisplayString,
    sysORUpTime     TimeStamp
}

sysORIndex OBJECT-TYPE
    SYNTAX      INTEGER (1..2147483647)
    ACCESS      not-accessible
    STATUS      mandatory
    DESCRIPTION 
        "The auxiliary variable used for identifying instances
         of the columnar objects in the sysORTable."
    ::= { sysOREntry 1 }

sysORID OBJECT-TYPE
    SYNTAX      OBJECT IDENTIFIER
    ACCESS      read-only
    STATUS      mandatory
    DESCRIPTION 
        "An authoritative identification of a capabilities
         statement with respect to various MIB modules supported
         by the local SNMP application acting as a command
         responder."
    ::= { sysOREntry 2 }

sysORDescr OBJECT-TYPE
    SYNTAX      DisplayString
    ACCESS      read-only
    STATUS      mandatory
    DESCRIPTION 
        "A textual description of the capabilities identified
         by the corresponding instance of sysORID."
    ::= { sysOREntry 3 }

sysORUpTime OBJECT-TYPE
    SYNTAX      TimeStamp
    ACCESS      read-only
    STATUS      mandatory
    DESCRIPTION 
        "The value of sysUpTime at the time this conceptual
         row was last instantiated."
    ::= { sysOREntry 4 }

snmp OBJECT IDENTIFIER
    ::= { mib-2 11 }

snmpInPkts OBJECT-TYPE
    SYNTAX      Counter
    ACCESS      read-only
    STATUS      mandatory
    DESCRIPTION 
        "The total number of messages delivered to the SNMP
         entity from the transport service."
    ::= { snmp 1 }

snmpOutPkts OBJECT-TYPE
    SYNTAX      Counter
    ACCESS      read-only
    STATUS      obsolete
    DESCRIPTION 
        "The total number of SNMP Messages which were
         passed from the SNMP protocol entity to the
         transport service."
    ::= { snmp 2 }

snmpInBadVersions OBJECT-TYPE
    SYNTAX      Counter
    ACCESS      read-only
    STATUS      mandatory
    DESCRIPTION 
        "The total number of SNMP messages which were delivered
         to the SNMP entity and were for an unsupported SNMP
         version."
    ::= { snmp 3 }

snmpInBadCommunityNames OBJECT-TYPE
    SYNTAX      Counter
    ACCESS      read-only
    STATUS      mandatory
    DESCRIPTION 
        "The total number of community-based SNMP messages (for
         example,  SNMPv1) delivered to the SNMP entity which
         used an SNMP community name not known to said entity.
         Also, implementations which authenticate community-based
         SNMP messages using check(s) in addition to matching
         the community name (for example, by also checking
         whether the message originated from a transport address
         allowed to use a specified community name) MAY include
         in this value the number of messages which failed the
         additional check(s).  It is strongly RECOMMENDED that
         
         
         
         the documentation for any security model which is used
         to authenticate community-based SNMP messages specify
         the precise conditions that contribute to this value."
    ::= { snmp 4 }

snmpInBadCommunityUses OBJECT-TYPE
    SYNTAX      Counter
    ACCESS      read-only
    STATUS      mandatory
    DESCRIPTION 
        "The total number of community-based SNMP messages (for
         example, SNMPv1) delivered to the SNMP entity which
         represented an SNMP operation that was not allowed for
         the SNMP community named in the message.  The precise
         conditions under which this counter is incremented
         (if at all) depend on how the SNMP entity implements
         its access control mechanism and how its applications
         interact with that access control mechanism.  It is
         strongly RECOMMENDED that the documentation for any
         access control mechanism which is used to control access
         to and visibility of MIB instrumentation specify the
         precise conditions that contribute to this value."
    ::= { snmp 5 }

snmpInASNParseErrs OBJECT-TYPE
    SYNTAX      Counter
    ACCESS      read-only
    STATUS      mandatory
    DESCRIPTION 
        "The total number of ASN.1 or BER errors encountered by
         the SNMP entity when decoding received SNMP messages."
    ::= { snmp 6 }

snmpInTooBigs OBJECT-TYPE
    SYNTAX      Counter
    ACCESS      read-only
    STATUS      obsolete
    DESCRIPTION 
        "The total number of SNMP PDUs which were
         delivered to the SNMP protocol entity and for
         which the value of the error-status field was
         `tooBig'."
    ::= { snmp 8 }

snmpInNoSuchNames OBJECT-TYPE
    SYNTAX      Counter
    ACCESS      read-only
    STATUS      obsolete
    DESCRIPTION 
        "The total number of SNMP PDUs which were
         delivered to the SNMP protocol entity and for
         which the value of the error-status field was
         `noSuchName'."
    ::= { snmp 9 }

snmpInBadValues OBJECT-TYPE
    SYNTAX      Counter
    ACCESS      read-only
    STATUS      obsolete
    DESCRIPTION 
        "The total number of SNMP PDUs which were
         delivered to the SNMP protocol entity and for
         which the value of the error-status field was
         `badValue'."
    ::= { snmp 10 }

snmpInReadOnlys OBJECT-TYPE
    SYNTAX      Counter
    ACCESS      read-only
    STATUS      obsolete
    DESCRIPTION 
        "The total number valid SNMP PDUs which were delivered
         to the SNMP protocol entity and for which the value
         of the error-status field was `readOnly'.  It should
         be noted that it is a protocol error to generate an
         SNMP PDU which contains the value `readOnly' in the
         error-status field, as such this object is provided
         as a means of detecting incorrect implementations of
         the SNMP."
    ::= { snmp 11 }

snmpInGenErrs OBJECT-TYPE
    SYNTAX      Counter
    ACCESS      read-only
    STATUS      obsolete
    DESCRIPTION 
        "The total number of SNMP PDUs which were delivered
         to the SNMP protocol entity and for which the value
         of the error-status field was `genErr'."
    ::= { snmp 12 }

snmpInTotalReqVars OBJECT-TYPE
    SYNTAX      Counter
    ACCESS      read-only
    STATUS      obsolete
    DESCRIPTION 
        "The total number of MIB objects which have been
         retrieved successfully by the SNMP protocol entity
         as the result of receiving valid SNMP Get-Request
         and Get-Next PDUs."
    ::= { snmp 13 }

snmpInTotalSetVars OBJECT-TYPE
    SYNTAX      Counter
    ACCESS      read-only
    STATUS      obsolete
    DESCRIPTION 
        "The total number of MIB objects which have been
         altered successfully by the SNMP protocol entity as
         the result of receiving valid SNMP Set-Request PDUs."
    ::= { snmp 14 }

snmpInGetRequests OBJECT-TYPE
    SYNTAX      Counter
    ACCESS      read-only
    STATUS      obsolete
    DESCRIPTION 
        "The total number of SNMP Get-Request PDUs which
         have been accepted and processed by the SNMP
         protocol entity."
    ::= { snmp 15 }

snmpInGetNexts OBJECT-TYPE
    SYNTAX      Counter
    ACCESS      read-only
    STATUS      obsolete
    DESCRIPTION 
        "The total number of SNMP Get-Next PDUs which have been
         accepted and processed by the SNMP protocol entity."
    ::= { snmp 16 }

snmpInSetRequests OBJECT-TYPE
    SYNTAX      Counter
    ACCESS      read-only
    STATUS      obsolete
    DESCRIPTION 
        "The total number of SNMP Set-Request PDUs which
         have been accepted and processed by the SNMP protocol
         entity."
    ::= { snmp 17 }

snmpInGetResponses OBJECT-TYPE
    SYNTAX      Counter
    ACCESS      read-only
    STATUS      obsolete
    DESCRIPTION 
        "The total number of SNMP Get-Response PDUs which
         have been accepted and processed by the SNMP protocol
         entity."
    ::= { snmp 18 }

snmpInTraps OBJECT-TYPE
    SYNTAX      Counter
    ACCESS      read-only
    STATUS      obsolete
    DESCRIPTION 
        "The total number of SNMP Trap PDUs which have been
         accepted and processed by the SNMP protocol entity."
    ::= { snmp 19 }

snmpOutTooBigs OBJECT-TYPE
    SYNTAX      Counter
    ACCESS      read-only
    STATUS      obsolete
    DESCRIPTION 
        "The total number of SNMP PDUs which were generated
         by the SNMP protocol entity and for which the value
         of the error-status field was `tooBig.'"
    ::= { snmp 20 }

snmpOutNoSuchNames OBJECT-TYPE
    SYNTAX      Counter
    ACCESS      read-only
    STATUS      obsolete
    DESCRIPTION 
        "The total number of SNMP PDUs which were generated
         by the SNMP protocol entity and for which the value
         of the error-status was `noSuchName'."
    ::= { snmp 21 }

snmpOutBadValues OBJECT-TYPE
    SYNTAX      Counter
    ACCESS      read-only
    STATUS      obsolete
    DESCRIPTION 
        "The total number of SNMP PDUs which were generated
         by the SNMP protocol entity and for which the value
         of the error-status field was `badValue'."
    ::= { snmp 22 }

snmpOutGenErrs OBJECT-TYPE
    SYNTAX      Counter
    ACCESS      read-only
    STATUS      obsolete
    DESCRIPTION 
        "The total number of SNMP PDUs which were generated
         by the SNMP protocol entity and for which the value
         of the error-status field was `genErr'."
    ::= { snmp 24 }

snmpOutGetRequests OBJECT-TYPE
    SYNTAX      Counter
    ACCESS      read-only
    STATUS      obsolete
    DESCRIPTION 
        "The total number of SNMP Get-Request PDUs which
         have been generated by the SNMP protocol entity."
    ::= { snmp 25 }

snmpOutGetNexts OBJECT-TYPE
    SYNTAX      Counter
    ACCESS      read-only
    STATUS      obsolete
    DESCRIPTION 
        "The total number of SNMP Get-Next PDUs which have
         been generated by the SNMP protocol entity."
    ::= { snmp 26 }

snmpOutSetRequests OBJECT-TYPE
    SYNTAX      Counter
    ACCESS      read-only
    STATUS      obsolete
    DESCRIPTION 
        "The total number of SNMP Set-Request PDUs which
         have been generated by the SNMP protocol entity."
    ::= { snmp 27 }

snmpOutGetResponses OBJECT-TYPE
    SYNTAX      Counter
    ACCESS      read-only
    STATUS      obsolete
    DESCRIPTION 
        "The total number of SNMP Get-Response PDUs which
         have been generated by the SNMP protocol entity."
    ::= { snmp 28 }

snmpOutTraps OBJECT-TYPE
    SYNTAX      Counter
    ACCESS      read-only
    STATUS      obsolete
    DESCRIPTION 
        "The total number of SNMP Trap PDUs which have
         been generated by the SNMP protocol entity."
    ::= { snmp 29 }

snmpEnableAuthenTraps OBJECT-TYPE
    SYNTAX      INTEGER { enabled(1), disabled(2) }
    ACCESS      read-write
    STATUS      mandatory
    DESCRIPTION 
        "Indicates whether the SNMP entity is permitted to
         generate authenticationFailure traps.  The value of this
         object overrides any configuration information; as such,
         it provides a means whereby all authenticationFailure
         traps may be disabled.
         
         Note that it is strongly recommended that this object
         be stored in non-volatile memory so that it remains
         constant across re-initializations of the network
         management system."
    ::= { snmp 30 }

snmpSilentDrops OBJECT-TYPE
    SYNTAX      Counter
    ACCESS      read-only
    STATUS      mandatory
    DESCRIPTION 
        "The total number of Confirmed Class PDUs (such as
         GetRequest-PDUs, GetNextRequest-PDUs,
         GetBulkRequest-PDUs, SetRequest-PDUs, and
         InformRequest-PDUs) delivered to the SNMP entity which
         were silently dropped because the size of a reply
         containing an alternate Response Class PDU (such as a
         Response-PDU) with an empty variable-bindings field
         was greater than either a local constraint or the
         maximum message size associated with the originator of
         the request."
    ::= { snmp 31 }

snmpProxyDrops OBJECT-TYPE
    SYNTAX      Counter
    ACCESS      read-only
    STATUS      mandatory
    DESCRIPTION 
        "The total number of Confirmed Class PDUs
         (such as GetRequest-PDUs, GetNextRequest-PDUs,
         GetBulkRequest-PDUs, SetRequest-PDUs, and
         InformRequest-PDUs) delivered to the SNMP entity which
         were silently dropped because the transmission of
         the (possibly translated) message to a proxy target
         failed in a manner (other than a time-out) such that
         no Response Class PDU (such as a Response-PDU) could
         be returned."
    ::= { snmp 32 }

snmpMIBObjects OBJECT IDENTIFIER
    ::= { snmpMIB 1 }

snmpTrap OBJECT IDENTIFIER
    ::= { snmpMIBObjects 4 }

snmpTrapOID OBJECT-TYPE
    SYNTAX      OBJECT IDENTIFIER
    ACCESS      read-only
    STATUS      mandatory
    DESCRIPTION 
        "The authoritative identification of the notification
         currently being sent.  This variable occurs as
         the second varbind in every SNMPv2-Trap-PDU and
         InformRequest-PDU."
    ::= { snmpTrap 1 }

snmpTrapEnterprise OBJECT-TYPE
    SYNTAX      OBJECT IDENTIFIER
    ACCESS      read-only
    STATUS      mandatory
    DESCRIPTION 
        "The authoritative identification of the enterprise
         associated with the trap currently being sent.  When an
         SNMP proxy agent is mapping an RFC1157 Trap-PDU
         into a SNMPv2-Trap-PDU, this variable occurs as the
         last varbind."
    ::= { snmpTrap 3 }

snmpTraps OBJECT IDENTIFIER
    ::= { snmpMIBObjects 5 }

snmpSet OBJECT IDENTIFIER
    ::= { snmpMIBObjects 6 }

snmpSetSerialNo OBJECT-TYPE
    SYNTAX      TestAndIncr
    ACCESS      read-write
    STATUS      mandatory
    DESCRIPTION 
        "An advisory lock used to allow several cooperating
         command generator applications to coordinate their
         use of the SNMP set operation.
         
         This object is used for coarse-grain coordination.
         To achieve fine-grain coordination, one or more similar
         objects might be defined within each MIB group, as
         appropriate."
    ::= { snmpSet 1 }

snmpMIBConformance OBJECT IDENTIFIER
    ::= { snmpMIB 2 }

snmpMIBCompliances OBJECT IDENTIFIER
    ::= { snmpMIBConformance 1 }

snmpMIBGroups OBJECT IDENTIFIER
    ::= { snmpMIBConformance 2 }

coldStart TRAP-TYPE
    ENTERPRISE  snmpTraps
--     STATUS      mandatory
    DESCRIPTION 
        "A coldStart trap signifies that the SNMP entity,
         supporting a notification originator application, is
         reinitializing itself and that its configuration may
         have been altered."
    ::= 1

warmStart TRAP-TYPE
    ENTERPRISE  snmpTraps
--     STATUS      mandatory
    DESCRIPTION 
        "A warmStart trap signifies that the SNMP entity,
         supporting a notification originator application,
         is reinitializing itself such that its configuration
         is unaltered."
    ::= 2

authenticationFailure TRAP-TYPE
    ENTERPRISE  snmpTraps
--     STATUS      mandatory
    DESCRIPTION 
        "An authenticationFailure trap signifies that the SNMP
         entity has received a protocol message that is not
         properly authenticated.  While all implementations
         of SNMP entities MAY be capable of generating this
         trap, the snmpEnableAuthenTraps object indicates
         whether this trap will be generated."
    ::= 5

snmpSetGroup OBJECT IDENTIFIER
    ::= { snmpMIBGroups 5 }

-- snmpSetGroup OBJECT-GROUP
--     OBJECTS     { snmpSetSerialNo }
--     STATUS      mandatory
--     DESCRIPTION 
--         "A collection of objects which allow several cooperating
--          command generator applications to coordinate their
--          use of the set operation."
--     ::= { snmpMIBGroups 5 }

systemGroup OBJECT IDENTIFIER
    ::= { snmpMIBGroups 6 }

-- systemGroup OBJECT-GROUP
--     OBJECTS     { sysDescr, sysObjectID, sysUpTime, sysContact, 
--                   sysName, sysLocation, sysServices, sysORLastChange, 
--                   sysORID, sysORUpTime, sysORDescr }
--     STATUS      mandatory
--     DESCRIPTION 
--         "The system group defines objects which are common to all
--          managed systems."
--     ::= { snmpMIBGroups 6 }

snmpBasicNotificationsGroup OBJECT IDENTIFIER
    ::= { snmpMIBGroups 7 }

-- snmpBasicNotificationsGroup NOTIFICATION-GROUP
--     NOTIFICATIONS { coldStart, authenticationFailure }
--     STATUS      mandatory
--     DESCRIPTION 
--         "The basic notifications implemented by an SNMP entity
--          supporting command responder applications."
--     ::= { snmpMIBGroups 7 }

snmpGroup OBJECT IDENTIFIER
    ::= { snmpMIBGroups 8 }

-- snmpGroup OBJECT-GROUP
--     OBJECTS     { snmpInPkts, snmpInBadVersions, snmpInASNParseErrs, 
--                   snmpSilentDrops, snmpProxyDrops, 
--                   snmpEnableAuthenTraps }
--     STATUS      mandatory
--     DESCRIPTION 
--         "A collection of objects providing basic instrumentation
--          and control of an SNMP entity."
--     ::= { snmpMIBGroups 8 }

snmpCommunityGroup OBJECT IDENTIFIER
    ::= { snmpMIBGroups 9 }

-- snmpCommunityGroup OBJECT-GROUP
--     OBJECTS     { snmpInBadCommunityNames, snmpInBadCommunityUses }
--     STATUS      mandatory
--     DESCRIPTION 
--         "A collection of objects providing basic instrumentation
--          of a SNMP entity which supports community-based
--          authentication."
--     ::= { snmpMIBGroups 9 }

snmpObsoleteGroup OBJECT IDENTIFIER
    ::= { snmpMIBGroups 10 }

-- snmpObsoleteGroup OBJECT-GROUP
--     OBJECTS     { snmpOutPkts, snmpInTooBigs, snmpInNoSuchNames, 
--                   snmpInBadValues, snmpInReadOnlys, snmpInGenErrs, 
--                   snmpInTotalReqVars, snmpInTotalSetVars, 
--                   snmpInGetRequests, snmpInGetNexts, 
--                   snmpInSetRequests, snmpInGetResponses, snmpInTraps, 
--                   snmpOutTooBigs, snmpOutNoSuchNames, 
--                   snmpOutBadValues, snmpOutGenErrs, 
--                   snmpOutGetRequests, snmpOutGetNexts, 
--                   snmpOutSetRequests, snmpOutGetResponses, 
--                   snmpOutTraps }
--     STATUS      obsolete
--     DESCRIPTION 
--         "A collection of objects from RFC 1213 made obsolete
--          by this MIB module."
--     ::= { snmpMIBGroups 10 }

snmpWarmStartNotificationGroup OBJECT IDENTIFIER
    ::= { snmpMIBGroups 11 }

-- snmpWarmStartNotificationGroup NOTIFICATION-GROUP
--     NOTIFICATIONS { warmStart }
--     STATUS      mandatory
--     DESCRIPTION 
--         "An additional notification for an SNMP entity supporting
--          command responder applications, if it is able to reinitialize
--          itself such that its configuration is unaltered."
--     ::= { snmpMIBGroups 11 }

snmpNotificationGroup OBJECT IDENTIFIER
    ::= { snmpMIBGroups 12 }

-- snmpNotificationGroup OBJECT-GROUP
--     OBJECTS     { snmpTrapOID, snmpTrapEnterprise }
--     STATUS      mandatory
--     DESCRIPTION 
--         "These objects are required for entities
--          which support notification originator applications."
--     ::= { snmpMIBGroups 12 }

snmpBasicCompliance OBJECT IDENTIFIER
    ::= { snmpMIBCompliances 2 }

-- snmpBasicCompliance MODULE-COMPLIANCE
--     STATUS      deprecated
--     DESCRIPTION 
--         "The compliance statement for SNMPv2 entities which
--          implement the SNMPv2 MIB.
--          
--          This compliance statement is replaced by
--          snmpBasicComplianceRev2."

--     MODULE      -- -- this module

--         MANDATORY-GROUPS        { snmpGroup, snmpSetGroup, 
--                   systemGroup, snmpBasicNotificationsGroup }

--         GROUP   snmpCommunityGroup
--         DESCRIPTION   
--               "This group is mandatory for SNMPv2 entities which
--                support community-based authentication."

--     ::= { snmpMIBCompliances 2 }

snmpBasicComplianceRev2 OBJECT IDENTIFIER
    ::= { snmpMIBCompliances 3 }

-- snmpBasicComplianceRev2 MODULE-COMPLIANCE
--     STATUS      mandatory
--     DESCRIPTION 
--         "The compliance statement for SNMP entities which
--          implement this MIB module."

--     MODULE      -- -- this module

--         MANDATORY-GROUPS        { snmpGroup, snmpSetGroup, 
--                   systemGroup, snmpBasicNotificationsGroup }

--         GROUP   snmpCommunityGroup
--         DESCRIPTION   
--               "This group is mandatory for SNMP entities which
--                support community-based authentication."

--         GROUP   snmpWarmStartNotificationGroup
--         DESCRIPTION   
--               "This group is mandatory for an SNMP entity which
--                supports command responder applications, and is
--                able to reinitialize itself such that its
--                configuration is unaltered."

--     ::= { snmpMIBCompliances 3 }

END -- end of module SNMPv2-MIB.
