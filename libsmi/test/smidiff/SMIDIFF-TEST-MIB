SMIDIFF-TEST-MIB DEFINITIONS ::= BEGIN

IMPORTS
    MODULE-IDENTITY
        FROM SNMPv2-SMI
    TEXTUAL-CONVENTION, DisplayString
	FROM SNMPv2-TC
    ibr
        FROM TUBS-SMI;

smidiffTestMib MODULE-IDENTITY
    LAST-UPDATED    "200109262300Z"
    ORGANIZATION    
            "TU Braunschweig"
    CONTACT-INFO    
            "        Frank Strauss
             
             Postal: TU Braunschweig
                     Muehlenpfordtstrasse 23
                     38106 Braunschweig
                     Germany
             
              Phone: +49 531 391-3283
              EMail: strauss@ibr.cs.tu-bs.de
               http://www.ibr.cs.tu-bs.de/~strauss/"
    DESCRIPTION     
            "This MIB module represents the toplevel module of
             a collection of MIB modules to check the capabilities
             of smidiff."
    REVISION        "200109262300Z"
    DESCRIPTION     
            "Initial Revision."
    ::= { ibr 10 }

MyDisplayString ::= TEXTUAL-CONVENTION
    STATUS    current
    DESCRIPTION
	" An Illegal use of a tc."
    SYNTAX    DisplayString
END
